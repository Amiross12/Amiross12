(defun array->pts (arr / lst pts)
  (setq lst (vlax-safearray->list arr)
        pts '())
  (while lst
    (setq pts (cons (list (car lst) (cadr lst) (caddr lst)) pts)
          lst (cdddr lst))
  )
  (reverse pts)
)

(defun c:CHAINDIM (/ p1 p2 doc ms lineObj ss i ent obj arr pts sorted j pa pb mid ang off pDim)
  (vl-load-com)
  (setq p1 (getpoint "\nבחר נקודת התחלה: ")
        p2 (getpoint p1 "\nבחר נקודת סיום: "))
  (if (and p1 p2)
    (progn
      (setq doc (vla-get-ActiveDocument (vlax-get-Acad-object))
            ms  (vla-get-ModelSpace doc)
            lineObj (vla-AddLine ms (vlax-3D-point p1) (vlax-3D-point p2))
            pts (list p1 p2)
      )
      (setq ss (ssget "F" (list p1 p2) '((0 . "LINE,LWPOLYLINE,ARC,CIRCLE"))))
      (if ss
        (progn
          (setq i 0)
          (while (< i (sslength ss))
            (setq ent (ssname ss i)
                  obj (vlax-ename->vla-object ent)
                  arr (vlax-invoke lineObj 'IntersectWith obj acExtendNone)
            )
            (if arr
              (foreach pt (array->pts arr)
                (if (not (member pt pts))
                  (setq pts (cons pt pts))
                )
              )
            )
            (setq i (1+ i))
          )
        )
      )
      (vla-delete lineObj)
      (setq sorted
        (vl-sort pts
          (function
            (lambda (a b)
              (< (distance p1 a) (distance p1 b))
            )
          )
        )
      )
      (setq off (* 0.1 (distance p1 p2)))
      (setq j 0)
      (while (< j (1- (length sorted)))
        (setq pa (nth j sorted)
              pb (nth (1+ j) sorted)
              mid (mapcar '(lambda (x y) (/ (+ x y) 2.0)) pa pb)
              ang (angle p1 p2)
              pDim (polar mid (+ ang (/ pi 2)) off)
        )
        (command "_DIMLINEAR" pa pb pDim)
        (setq j (1+ j))
      )
    )
  )
  (princ)
)
